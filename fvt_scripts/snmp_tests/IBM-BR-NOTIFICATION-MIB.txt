IBM-BR-NOTIFICATION-MIB DEFINITIONS ::= BEGIN

-- Copyright (c) 2015-2021 Contributors to the Eclipse Foundation
-- See the NOTICE file(s) distributed with this work for additional
-- information regarding copyright ownership.
-- This program and the accompanying materials are made available under the
-- terms of the Eclipse Public License 2.0 which is available at
-- http://www.eclipse.org/legal/epl-2.0
-- SPDX-License-Identifier: EPL-2.0


IMPORTS
    enterprises, MODULE-IDENTITY, OBJECT-TYPE,
    NOTIFICATION-TYPE, Unsigned32
        FROM SNMPv2-SMI
    DisplayString
        FROM SNMPv2-TC;

ibmBrNotificationMIB MODULE-IDENTITY
    LAST-UPDATED "201107120000Z"
    ORGANIZATION "IBM Corporation"
    CONTACT-INFO "BR consumer must provide contact info"
    DESCRIPTION "The MIB module for notifications generated by the IBM Appliance Platform Component."
    REVISION "201107120000Z"
    DESCRIPTION "Created"
    ::= { ibmBrManagement 1 }

ibm OBJECT IDENTIFIER ::= { enterprises 2 }
ibmProd OBJECT IDENTIFIER ::= { ibm 6 }
ibmAppliancePlatformMib OBJECT IDENTIFIER ::= { ibmProd 234 }
ibmBrHardware OBJECT IDENTIFIER ::= { ibmAppliancePlatformMib 1 }
ibmBrManagement OBJECT IDENTIFIER ::= { ibmBrHardware 1 }
ibmBrNotifications OBJECT IDENTIFIER ::= { ibmBrManagement 2 }
ibmBrSensorNotifications OBJECT IDENTIFIER ::= { ibmBrNotifications 1 }
ibmBrSensorNotificationElements OBJECT IDENTIFIER ::= { ibmBrSensorNotifications 1 }
ibmBrSensorNotificationDefinitions OBJECT IDENTIFIER ::= { ibmBrSensorNotifications 2 }
ibmBrSensorNotificationDefinitionsPrefix OBJECT IDENTIFIER ::= { ibmBrSensorNotificationDefinitions 0 }


ibmBrSensorNotificationTime OBJECT-TYPE
    SYNTAX      DisplayString
    MAX-ACCESS  accessible-for-notify
    STATUS      current
    DESCRIPTION
       "The date and time when the sensor-related event occurred"
    ::= { ibmBrSensorNotificationElements 1 }

ibmBrSensorNotificationSensorType OBJECT-TYPE
    SYNTAX      INTEGER {
                          temperature(1),
                          voltage(2),
                          fan(4),
                          powerSupply(8)
                        }
    MAX-ACCESS  accessible-for-notify
    STATUS      current
    DESCRIPTION
       "The type of the sensor that caused the sensor-related event"
    ::= { ibmBrSensorNotificationElements 2 }

ibmBrSensorNotificationSensorNum OBJECT-TYPE
    SYNTAX      Unsigned32
    MAX-ACCESS  accessible-for-notify
    STATUS      current
    DESCRIPTION
       "The sensor number that caused the sensor-related event"
    ::= { ibmBrSensorNotificationElements 3 }

ibmBrSensorNotificationSensorName OBJECT-TYPE
    SYNTAX      DisplayString
    MAX-ACCESS  accessible-for-notify
    STATUS      current
    DESCRIPTION
       "The name of the sensor that caused the sensor-related event"
    ::= { ibmBrSensorNotificationElements 4 }

ibmBrSensorNotificationSensorEventReadingTypeCode OBJECT-TYPE
    SYNTAX      DisplayString
    MAX-ACCESS  accessible-for-notify
    STATUS      current
    DESCRIPTION
       "The state of the sensor that caused the sensor-related event"
    ::= { ibmBrSensorNotificationElements 5 }

ibmBrSensorNotificationSensorEventDirection OBJECT-TYPE
    SYNTAX      INTEGER {
                          none(1),
                          asserted(2),
                          deasserted(3)
                        }
    MAX-ACCESS  accessible-for-notify
    STATUS      current
    DESCRIPTION
       "The direction of the sensor-related event"
    ::= { ibmBrSensorNotificationElements 6 }


ibmBrSensorNotificationFanOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a fan sensor has transitioned back to the OK state."
    ::= { ibmBrSensorNotificationDefinitionsPrefix 1 }

ibmBrSensorNotificationFanNotOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a fan sensor has transitioned to an undesirable state."
    ::= { ibmBrSensorNotificationDefinitionsPrefix 2 }

ibmBrSensorNotificationVoltageOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a voltage sensor has transitioned back to the OK state."
    ::= { ibmBrSensorNotificationDefinitionsPrefix 3 }

ibmBrSensorNotificationVoltageNotOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a voltage sensor has transitioned to an undesirable state."
    ::= { ibmBrSensorNotificationDefinitionsPrefix 4 }

ibmBrSensorNotificationTempOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a temperature sensor has transitioned back to the OK state."
    ::= { ibmBrSensorNotificationDefinitionsPrefix 5 }

ibmBrSensorNotificationTempNotOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a temperature sensor has transitioned to an undesirable state."
    ::= { ibmBrSensorNotificationDefinitionsPrefix 6 }

ibmBrSensorNotificationPowerSupplyOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a power supply sensor has transitioned back to the OK state."
    ::= { ibmBrSensorNotificationDefinitionsPrefix 7 }

ibmBrSensorNotificationPowerSupplyNotOk NOTIFICATION-TYPE
    OBJECTS {
        ibmBrSensorNotificationTime,
        ibmBrSensorNotificationSensorType,
        ibmBrSensorNotificationSensorNum,
        ibmBrSensorNotificationSensorName,
        ibmBrSensorNotificationSensorEventReadingTypeCode,
        ibmBrSensorNotificationSensorEventDirection    }
    STATUS current
    DESCRIPTION
        "This notification indicates that a power supply sensor has transitioned to an undesirable state."
    ::= { ibmBrSensorNotificationDefinitionsPrefix 8 }

END
