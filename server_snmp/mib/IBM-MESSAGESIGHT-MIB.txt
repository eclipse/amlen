IBM-MESSAGESIGHT-MIB DEFINITIONS ::= BEGIN
-- A Comment!
--
-- Eclipse Amlen MIB File
--

-- IMPORTS: Include definitions from other mibs here, which is always
-- the first item in a MIB file.
IMPORTS
	OBJECT-TYPE,
	Integer32,
	enterprises,
	Gauge32,
	NOTIFICATION-TYPE, 
	MODULE-IDENTITY
		FROM SNMPv2-SMI   -- RFC2578

	DisplayString
		FROM SNMPv2-TC
		
	CounterBasedGauge64
        FROM HCNUM-TC     -- RFC2856

	MODULE-COMPLIANCE, OBJECT-GROUP,
	NOTIFICATION-GROUP
		FROM SNMPv2-CONF; -- RFC2580

--
-- A brief description and update information about this mib.
--

ibmMessageSightMIB MODULE-IDENTITY
	LAST-UPDATED "201808160000Z"            -- 16 Aug. 2018, midnight
	ORGANIZATION "IBM"
	CONTACT-INFO "Contact the Eclipse Amlen Developers"
	DESCRIPTION  "This file defines the private Amlen MIB extensions
	              used to get status and receive traps from MessageSight."
	REVISION "201808160000Z"
	DESCRIPTION "Updated"

	::= {ibmProd  253}

ibm OBJECT IDENTIFIER ::= { enterprises 2 }
ibmProd OBJECT IDENTIFIER ::= { ibm 6 }

-- MessageSight Node definitions  

-- MessageSight conformance information
ibmImaMIBConformance OBJECT IDENTIFIER ::= {ibmMessageSightMIB 2}
ibmImaMIBCompliances OBJECT IDENTIFIER ::= {ibmImaMIBConformance 1}
ibmImaMIBGourps OBJECT IDENTIFIER ::= {ibmImaMIBConformance 2}

-- compliance statements of MessageSight MIB
ibmImaMIBCompliance MODULE-COMPLIANCE
	  STATUS current
	  DESCRIPTION 
	    "The compliance statement for IBM MessageSight entities which
               implement ibmMessageSightMIB."
    MODULE  -- this module
        MANDATORY-GROUPS { ibmImaStatusServerGroup,
                           ibmImaStatisticsMemoryGroup,
                           ibmImaStatisticsStoreGroup,
                           ibmImaStatisticsServerGroup,
                           ibmImaEndpointGroup,
                           ibmImaSubscriptionGroup,
                           ibmImaConnectionGroup,
                           ibmImaTopicGroup,
                           ibmImaNotificationCommonGroup,
                           ibmImaNotificationMemoryGroup,
                           ibmImaNotificationMemoryCtrlGroup,
                           ibmImaMemoryNotificationGroup,
                           ibmImaNotificationStoreGroup,
                           ibmImaNotificationStoreCtrlGroup,
                           ibmImaStoreNotificationGroup }
	  ::= {ibmImaMIBCompliances 1}

-- units of conformance

ibmImaStatusServerGroup OBJECT-GROUP
	OBJECTS { ibmImaServerState, 
			  ibmImaServerStateDesc,
			  ibmImaServerAdminStateReasonCode, 
			  ibmImaServerUpTime, 
			  ibmImaServerUpTimeDesc, 
			  ibmImaServerHAEnable, 
			  ibmImaServerHANewRole, 
			  ibmImaServerHAOldRole, 
			  ibmImaServerActiveNodes,
			  ibmImaServerSyncNodes, 
			  ibmImaServerPrimaryLastTime, 
			  ibmImaServerSyncCompletionPercent, 
			  ibmImaServerReasonCode }  
	STATUS current
	DESCRIPTION "IBM MessageSight server-related statistics."
	::= {ibmImaMIBGourps 1}
	
ibmImaStatisticsMemoryGroup OBJECT-GROUP
	OBJECTS { ibmImaMemoryTotalBytes, 
	          ibmImaMemoryFreeBytes, 
	          ibmImaMemoryFreePercent,
			  ibmImaServerVirtualMemoryBytes, 
			  ibmImaServerResidentSetBytes,
			  ibmImaMessagePayloads, 
			  ibmImaPublishSubscribe, 
			  ibmImaDestinations,
			  ibmImaCurrentActivity, 
			  ibmImaClientStates }  
	STATUS current
	DESCRIPTION "IBM MessageSight memory-related statistics."
	::= {ibmImaMIBGourps 2}

ibmImaStatisticsStoreGroup OBJECT-GROUP
	OBJECTS { ibmImaStoreMemoryUsedPercent, 
	          ibmImaStoreDiskUsedPercent, 
	          ibmImaStoreDiskFreeBytes,
	          ibmImaStoreMemoryTotalBytes,
	          ibmImaStorePool1TotalBytes,
	          ibmImaStorePool1UsedBytes,
	          ibmImaStorePool1UsedPercent,
	          ibmImaStorePool1RecordsLimitBytes,
	          ibmImaStorePool1RecordsUsedBytes,
	          ibmImaStorePool2TotalBytes,
	          ibmImaStorePool2UsedBytes,
	          ibmImaStorePool2UsedPercent }  
	STATUS current
	DESCRIPTION "IBM MessageSight store-related statistics."
	::= {ibmImaMIBGourps 3}
	
ibmImaStatisticsServerGroup OBJECT-GROUP
	OBJECTS { ibmImaActiveConnections, 
	          ibmImaTotalConnections, 
	          ibmImaReadMessages,
	          ibmImaWriteMessages,
	          ibmImaReadBytes,
	          ibmImaWriteBytes,
	          ibmImaBadConnections,
	          ibmImaTotalEndpoints,
	          ibmImaBufferedMessages,
	          ibmImaRetainedMessages,
	          ibmImaExpiredMessages }  
	STATUS current
	DESCRIPTION "Connection volume statistics."
	::= {ibmImaMIBGourps 4}
	
ibmImaEndpointGroup OBJECT-GROUP
	OBJECTS { ibmImaEndpointColIndex, 
	          ibmImaEndpointName, 
	          ibmImaEndpointIpAddr,
	          ibmImaEndpointEnabled,
	          ibmImaEndpointTotal,
	          ibmImaEndpointActive,
	          ibmImaEndpointMessages,
	          ibmImaEndpointBytes,
	          ibmImaEndpointLastErrorCode,
	          ibmImaEndpointConfigTime,
	          ibmImaEndpointResetTime,
	          ibmImaEndpointBadConnections }  
	STATUS current
	DESCRIPTION "Endpoint table statistics."
	::= {ibmImaMIBGourps 5}
	
ibmImaSubscriptionGroup OBJECT-GROUP
	OBJECTS { ibmImaSubscriptionColIndex, 
	          ibmImaSubscriptionSubName, 
	          ibmImaSubscriptionTopicString,
	          ibmImaSubscriptionClientID,
	          ibmImaSubscriptionIsDurable,
	          ibmImaSubscriptionBufferedMsgs,
	          ibmImaSubscriptionBufferedMsgsHWM,
	          ibmImaSubscriptionBufferedPercent,
	          ibmImaSubscriptionMaxMessages,
	          ibmImaSubscriptionPublishedMsgs,
	          ibmImaSubscriptionRejectedMsgs,
	          ibmImaSubscriptionBufferedHWMPercent,
	          ibmImaSubscriptionIsShared,
	          ibmImaSubscriptionConsumers,
	          ibmImaSubscriptionDiscardedMsgs,
	          ibmImaSubscriptionExpiredMsgs,
	          ibmImaSubscriptionMessagingPolicy }  
	STATUS current
	DESCRIPTION "Subscription table statistics."
	::= {ibmImaMIBGourps 6}
	
ibmImaConnectionGroup OBJECT-GROUP
	OBJECTS { ibmImaConnectionColIndex, 
	          ibmImaConnectionName, 
	          ibmImaConnectionProtocol,
	          ibmImaConnectionClientAddr,
	          ibmImaConnectionUserId,
	          ibmImaConnectionEndpoint,
	          ibmImaConnectionPort,
	          ibmImaConnectionConnectTime,
	          ibmImaConnectionDuration,
	          ibmImaConnectionReadBytes,
	          ibmImaConnectionReadMsg,
	          ibmImaConnectionWriteBytes,
	          ibmImaConnectionWriteMsg }  
	STATUS current
	DESCRIPTION "Connection table statistics."
	::= {ibmImaMIBGourps 7}
	
ibmImaTopicGroup OBJECT-GROUP
	OBJECTS { ibmImaTopicColIndex, 
	          ibmImaTopicTopicString, 
	          ibmImaTopicSubscriptions,
	          ibmImaTopicResetTime,
	          ibmImaTopicPublishedMsgs,
	          ibmImaTopicRejectedMsgs,
	          ibmImaTopicFailedPublishes }  
	STATUS current
	DESCRIPTION "Topic table statistics."
	::= {ibmImaMIBGourps 8}
	
ibmImaNotificationCommonGroup OBJECT-GROUP
	OBJECTS { ibmImaNotificationImaVersion , 
	          ibmImaNotificationImaNodeName , 
	          ibmImaNotificationEventTime ,
	          ibmImaNotificationObjectType  }  
	STATUS current
	DESCRIPTION "Common nofitication statistics."
	::= {ibmImaMIBGourps 9}
	
ibmImaNotificationMemoryGroup OBJECT-GROUP
	OBJECTS { ibmImaNotificationMemoryTotalBytes , 
	          ibmImaNotificationMemoryFreeBytes , 
	          ibmImaNotificationMemoryFreePercent ,
	          ibmImaNotificationVirtualMemoryBytes ,
	          ibmImaNotificationResidentSetBytes ,
	          ibmImaNotificationMessagePayloads ,
	          ibmImaNotificationPublishSubscribe ,
	          ibmImaNotificationDestinations ,
	          ibmImaNotificationCurrentActivity ,
	          ibmImaNotificationClientStates  }  
	STATUS current
	DESCRIPTION "Memory nofitication statistics."
	::= {ibmImaMIBGourps 10}
	
ibmImaNotificationMemoryCtrlGroup OBJECT-GROUP
	OBJECTS { ibmImaMemoryUsageWarningEnable , 
	          ibmImaMemoryUsageWarningThreshold , 
	          ibmImaMemoryUsageAlertEnable ,
	          ibmImaMemoryUsageAlertThreshold ,
	          ibmImaMemoryUsageWarningDuration  }  
	STATUS current
	DESCRIPTION "Memory nofitication control parameters."
	::= {ibmImaMIBGourps 11}
	
ibmImaMemoryNotificationGroup NOTIFICATION-GROUP
	NOTIFICATIONS  { ibmImaNotificationMemoryUsageWarning , 
	          ibmImaNotificationMemoryUsageAlert  }  
	STATUS current
	DESCRIPTION "Memory nofitications."
	::= {ibmImaMIBGourps 12}
	
ibmImaNotificationStoreGroup OBJECT-GROUP
	OBJECTS { ibmImaNotificationStoreDiskUsedPercent , 
	          ibmImaNotificationStoreDiskFreeBytes , 
	          ibmImaNotificationStoreMemoryUsedPercent ,
	          ibmImaNotificationStoreMemoryTotalBytes ,
	          ibmImaNotificationStorePool1TotalBytes ,
	          ibmImaNotificationStorePool1UsedBytes ,
	          ibmImaNotificationStorePool1UsedPercent ,
	          ibmImaNotificationStorePool1RecordsLimitBytes ,
	          ibmImaNotificationStorePool1RecordsUsedBytes ,
	          ibmImaNotificationStorePool2TotalBytes ,
	          ibmImaNotificationStorePool2UsedBytes ,
	          ibmImaNotificationStorePool2UsedPercent  }  
	STATUS current
	DESCRIPTION "Store nofitication statistics."
	::= {ibmImaMIBGourps 13}
	
ibmImaNotificationStoreCtrlGroup OBJECT-GROUP
	OBJECTS { ibmImaStoreDiskUsageWarningEnable , 
	          ibmImaStoreDiskUsageWarningThreshold , 
	          ibmImaStoreDiskUsageAlertEnable ,
	          ibmImaStoreDiskUsageAlertThreshold ,
	          ibmImaStoreDiskUsageWarningDuration ,
	          ibmImaStorePool1MemoryLowAlertEnable ,
	          ibmImaStorePool1MemoryLowAlertThreshold  }  
	STATUS current
	DESCRIPTION "Store nofitication control parameters."
	::= {ibmImaMIBGourps 14}
	
ibmImaStoreNotificationGroup NOTIFICATION-GROUP
	NOTIFICATIONS  { ibmImaNotificationStoreDiskUsageWarning , 
	          ibmImaNotificationStoreDiskUsageAlert ,
	          ibmImaNotificationStorePool1MemoryLowAlert  }  
	STATUS current
	DESCRIPTION "Store nofitications."
	::= {ibmImaMIBGourps 15}
	
ibmImaManagement OBJECT IDENTIFIER ::= {ibmMessageSightMIB 3}

ibmImaStatus OBJECT IDENTIFIER ::= {ibmImaManagement 1}

ibmImaStatusServer	OBJECT IDENTIFIER ::= {ibmImaStatus 1}
	
ibmImaServerState OBJECT-TYPE
	SYNTAX      Integer32 (0..14)
	MAX-ACCESS  read-only
	STATUS      current
	DESCRIPTION
	"IBM MessageSight server state.  The state is one of the following:
	State  Description of state
	-----  -------------------------
    0      Initializing
    1      Running (production)
    2      Stopping
    3      Initialized
    4      Transport started
    5      Protocol started
    6      Store started
    7      Engine started
    8      Messaging started
    9      Running (maintenance)
    10     Standby
    11     Store Starting
    12     Server starting
    13     Server stopped
    14     Unknown"
	::= {ibmImaStatusServer 1}		
		 
ibmImaServerStateDesc OBJECT-TYPE
	SYNTAX      DisplayString (SIZE (0..100))
	MAX-ACCESS  read-only
	STATUS      current
	DESCRIPTION
	"Description of the IBM MessageSight server state."
	::= {ibmImaStatusServer 2}		
		 
ibmImaServerAdminStateReasonCode OBJECT-TYPE
	SYNTAX      Integer32
	MAX-ACCESS  read-only
	STATUS      current
	DESCRIPTION
	"If an error occurred while starting the IBM MessageSight server, 
	provides an error code."
	::= {ibmImaStatusServer 3}
	
ibmImaServerUpTime OBJECT-TYPE
	SYNTAX      Integer32
	MAX-ACCESS  read-only
	STATUS      current
	DESCRIPTION
	"IBM MessageSight server up time in seconds."
	::= {ibmImaStatusServer 4}		
		 
ibmImaServerUpTimeDesc OBJECT-TYPE
	SYNTAX      DisplayString (SIZE (0..255))
	MAX-ACCESS  read-only
	STATUS      current
	DESCRIPTION
	"IBM MessageSight server up time in the format: 
	d days h hours m minutes s seconds."
	::= {ibmImaStatusServer 5}		
		 
ibmImaServerHAEnable OBJECT-TYPE
	SYNTAX      DisplayString (SIZE (0..100))
	MAX-ACCESS  read-only
	STATUS      current
	DESCRIPTION
	"High Availability enabled flag (1 if enabled, 0 otherwise)."
	::= {ibmImaStatusServer 6}		
		 
ibmImaServerHANewRole OBJECT-TYPE
	SYNTAX      DisplayString (SIZE (0..100))
	MAX-ACCESS  read-only
	STATUS      current
	DESCRIPTION
	"The current high availability role of this node. 
	Role      Description of role
	-------   -------------------
	PRIMARY   The primary appliance in a high availability pair
	STANDBY   The standby appliance in a high availability pair
	UNSYNC    The node is out of synchronization with the primary appliance
    TERMINATE The node was terminated by the primary (coordinated shutdown)
    ERROR     The node got out of synchronization due to a fatal error."
	::= {ibmImaStatusServer 7}		
		 
ibmImaServerHAOldRole OBJECT-TYPE
	SYNTAX      DisplayString (SIZE (0..100))
	MAX-ACCESS  read-only
	STATUS      current
	DESCRIPTION
	"The previous high availability role of this node. 
    Role      Description of role
    -------   -------------------
    PRIMARY   The primary appliance in a high availability pair
    STANDBY   The standby appliance in a high availability pair
    UNSYNC    The node is out of synchronization with the Primary 
    TERMINATE The node was terminated by the Primary (coordinated shutdown)
    ERROR     The node got out of synchronization due to a fatal error."
	::= {ibmImaStatusServer 8}		
		 
ibmImaServerActiveNodes OBJECT-TYPE
	SYNTAX      Integer32
	MAX-ACCESS  read-only
	STATUS      current
	DESCRIPTION
	"The number of active nodes in this high availability pair."
	::= {ibmImaStatusServer 9}		
		 
ibmImaServerSyncNodes OBJECT-TYPE
	SYNTAX      Integer32
	MAX-ACCESS  read-only
	STATUS      current
	DESCRIPTION
	"The number of synchronized nodes in this high availability pair."
	::= {ibmImaStatusServer 10}		
		 
ibmImaServerPrimaryLastTime OBJECT-TYPE
	SYNTAX      DisplayString (SIZE (0..255))
	MAX-ACCESS  read-only
	STATUS      current
	DESCRIPTION
	"An ISO-formatted time stamp indicating the last time that this node
	was the primary node."
	::= {ibmImaStatusServer 11}		
		 
ibmImaServerSyncCompletionPercent OBJECT-TYPE
	SYNTAX      Gauge32 (0..100)
	MAX-ACCESS  read-only
	STATUS      current
	DESCRIPTION
	"A value that is greater than zero indicates that this node is the primary node in a high availability
	pair and is synchronizing with the standby. Contains the 
	percentage of the synchronization which is complete."
	::= {ibmImaStatusServer 12}		
		 
ibmImaServerReasonCode OBJECT-TYPE
	SYNTAX      Integer32
	MAX-ACCESS  read-only
	STATUS      current
	DESCRIPTION
	"If a high availability error occurred, provides an error code."
	::= {ibmImaStatusServer 13}		

ibmImaStatisticsMemory	OBJECT IDENTIFIER ::= {ibmImaStatus 2}

ibmImaMemoryTotalBytes OBJECT-TYPE
	SYNTAX      CounterBasedGauge64
	MAX-ACCESS  read-only
	STATUS      current
	DESCRIPTION
	"The total amount of physical memory on IBM MessageSight."
	::= {ibmImaStatisticsMemory 1}

ibmImaMemoryFreeBytes OBJECT-TYPE
	SYNTAX      CounterBasedGauge64
	MAX-ACCESS  read-only
	STATUS      current
	DESCRIPTION
	"The amount of physical memory that is available."
	::= {ibmImaStatisticsMemory 2}
	
ibmImaMemoryFreePercent OBJECT-TYPE
	SYNTAX      Gauge32 (0..100)
	MAX-ACCESS  read-only
	STATUS      current
	DESCRIPTION
	"The amount of free memory as a percentage of the total physical memory."
	::= {ibmImaStatisticsMemory 3}
	
ibmImaServerVirtualMemoryBytes OBJECT-TYPE
	SYNTAX      CounterBasedGauge64
	MAX-ACCESS  read-only
	STATUS      current
	DESCRIPTION
	"The amount of virtual memory that is being used by IBM 
	MessageSight."
	::= {ibmImaStatisticsMemory 4}
	
ibmImaServerResidentSetBytes OBJECT-TYPE
	SYNTAX      CounterBasedGauge64
	MAX-ACCESS  read-only
	STATUS      current
	DESCRIPTION
	"The amount of physical memory that is being used by IBM 
	MessageSight."
	::= {ibmImaStatisticsMemory 5}
	
ibmImaMessagePayloads OBJECT-TYPE
	SYNTAX      CounterBasedGauge64 
	MAX-ACCESS  read-only
	STATUS      current
	DESCRIPTION
	"The amount of memory, in bytes, that is being used by IBM MessageSight 
	for message payloads."
	::= {ibmImaStatisticsMemory 6} 
	
ibmImaPublishSubscribe OBJECT-TYPE
	SYNTAX      CounterBasedGauge64 
	MAX-ACCESS  read-only
	STATUS      current
	DESCRIPTION
	"The amount of memory, in bytes, that is being used by IBM 
	MessageSight for publish/subscribe messaging."
	::= {ibmImaStatisticsMemory 7} 
	
ibmImaDestinations OBJECT-TYPE
	SYNTAX      CounterBasedGauge64 
	MAX-ACCESS  read-only
	STATUS      current
	DESCRIPTION
	"The amount of memory, in bytes, that is being used by IBM 
	MessageSight for destinations.  That is, for queues and topics."
	::= {ibmImaStatisticsMemory 8}
	
ibmImaCurrentActivity OBJECT-TYPE
	SYNTAX      CounterBasedGauge64
	MAX-ACCESS  read-only
	STATUS      current
	DESCRIPTION
	"The amount of memory, in bytes, that is being used by IBM 
	MessageSight for current activity.  Memory that is allocated in this 
	category includes sessions, transactions, message acknowledgments, 
	and monitoring request information."
	::= {ibmImaStatisticsMemory 9} 
	
ibmImaClientStates OBJECT-TYPE
	SYNTAX      CounterBasedGauge64
	MAX-ACCESS  read-only
	STATUS      current
	DESCRIPTION
	"The amount of memory, in bytes, that is being used by IBM 
    MessageSight for connected and disconnected clients."
	::= {ibmImaStatisticsMemory 10}


ibmImaStatisticsStore	OBJECT IDENTIFIER ::= {ibmImaStatus 3}

ibmImaStoreDiskUsedPercent OBJECT-TYPE
	SYNTAX      Gauge32 (0..100)
	MAX-ACCESS  read-only
	STATUS      current
	DESCRIPTION
	"The percentage of disk space that is used."
	::= {ibmImaStatisticsStore 1} 

ibmImaStoreDiskFreeBytes OBJECT-TYPE
	SYNTAX      CounterBasedGauge64
	MAX-ACCESS  read-only
	STATUS      current
	DESCRIPTION
	"The amount of disk space, in bytes, that is available."
	::= {ibmImaStatisticsStore 2} 
	
ibmImaStoreMemoryUsedPercent OBJECT-TYPE
	SYNTAX      Gauge32 (0..100)
	MAX-ACCESS  read-only
	STATUS      current
	DESCRIPTION
	"The percentage of persistent memory that is used, and, therefore, is 
	not available."
	::= {ibmImaStatisticsStore 3} 

ibmImaStoreMemoryTotalBytes OBJECT-TYPE
	SYNTAX      CounterBasedGauge64
	MAX-ACCESS  read-only
	STATUS      current
	DESCRIPTION
	"The total amount of persistent memory, in bytes, on IBM MessageSight."
	::= {ibmImaStatisticsStore 4}
	
ibmImaStorePool1TotalBytes OBJECT-TYPE
	SYNTAX      CounterBasedGauge64
	MAX-ACCESS  read-only
	STATUS      current
	DESCRIPTION
	"The amount of memory, in bytes, in pool 1."
	::= {ibmImaStatisticsStore 5}
	
ibmImaStorePool1UsedBytes OBJECT-TYPE
	SYNTAX      CounterBasedGauge64
	MAX-ACCESS  read-only
	STATUS      current
	DESCRIPTION
	"The amount of memory, in bytes, that is currently in use in pool 1."
	::= {ibmImaStatisticsStore 6}
	
ibmImaStorePool1UsedPercent OBJECT-TYPE
	SYNTAX      Gauge32 (0..100)
	MAX-ACCESS  read-only
	STATUS      current
	DESCRIPTION
	"The percentage of memory that is in use in pool 1."
	::= {ibmImaStatisticsStore 7}
	
ibmImaStorePool1RecordsLimitBytes OBJECT-TYPE
	SYNTAX      CounterBasedGauge64
	MAX-ACCESS  read-only
	STATUS      current
	DESCRIPTION
	"The overall amount of memory, in bytes, that can be used by client 
	applications."
	::= {ibmImaStatisticsStore 8}
	
ibmImaStorePool1RecordsUsedBytes OBJECT-TYPE
	SYNTAX      CounterBasedGauge64
	MAX-ACCESS  read-only
	STATUS      current
	DESCRIPTION
	"The amount of memory, in bytes, that is being used for client 
	records."
	::= {ibmImaStatisticsStore 9}
	
ibmImaStorePool2TotalBytes OBJECT-TYPE
	SYNTAX      CounterBasedGauge64
	MAX-ACCESS  read-only
	STATUS      current
	DESCRIPTION
	"The amount of memory, in bytes, in pool 2"
	::= {ibmImaStatisticsStore 10}
	
ibmImaStorePool2UsedBytes OBJECT-TYPE
	SYNTAX      CounterBasedGauge64
	MAX-ACCESS  read-only
	STATUS      current
	DESCRIPTION
	"The amount of memory, in bytes, that is currently in use in pool 2."
	::= {ibmImaStatisticsStore 11}
	
ibmImaStorePool2UsedPercent OBJECT-TYPE
	SYNTAX      Gauge32 (0..100)
	MAX-ACCESS  read-only
	STATUS      current
	DESCRIPTION
	"The percentage of memory that is in use in pool 2."
	::= {ibmImaStatisticsStore 12}

ibmImaStatisticsServer	OBJECT IDENTIFIER ::= {ibmImaStatus 4}
	
ibmImaActiveConnections OBJECT-TYPE
	SYNTAX      CounterBasedGauge64
	MAX-ACCESS  read-only
	STATUS      current
	DESCRIPTION
	"The current count of connections that are open."
	::= {ibmImaStatisticsServer 1}
	
ibmImaTotalConnections OBJECT-TYPE
	SYNTAX      CounterBasedGauge64
	MAX-ACCESS  read-only
	STATUS      current
	DESCRIPTION
	"The total count of connections that were accepted by IBM MessageSight 
	since the server was started."
	::= {ibmImaStatisticsServer 2}
	
ibmImaReadMessages OBJECT-TYPE
	SYNTAX      CounterBasedGauge64
	MAX-ACCESS  read-only
	STATUS      current
	DESCRIPTION
	"The count of incoming messages on all connections."
	::= {ibmImaStatisticsServer 3}

ibmImaWriteMessages OBJECT-TYPE
	SYNTAX      CounterBasedGauge64
	MAX-ACCESS  read-only
	STATUS      current
	DESCRIPTION
	"The count of outgoing messages on all connections."
	::= {ibmImaStatisticsServer 4}

ibmImaReadBytes OBJECT-TYPE
	SYNTAX      CounterBasedGauge64
	MAX-ACCESS  read-only
	STATUS      current
	DESCRIPTION
	"The number of bytes of incoming data on all connections."
	::= {ibmImaStatisticsServer 5}
	
ibmImaWriteBytes OBJECT-TYPE
	SYNTAX      CounterBasedGauge64
	MAX-ACCESS  read-only
	STATUS      current
	DESCRIPTION
	"The number of bytes of outgoing data on all connections."
	::= {ibmImaStatisticsServer 6}	
	
ibmImaBadConnections OBJECT-TYPE
	SYNTAX      CounterBasedGauge64
	MAX-ACCESS  read-only
	STATUS      current
	DESCRIPTION
	"The count of client connections where a physical connection is 
	established, but where messages cannot be sent or received."
	::= {ibmImaStatisticsServer 7}	
	
ibmImaTotalEndpoints OBJECT-TYPE
	SYNTAX      CounterBasedGauge64
	MAX-ACCESS  read-only
	STATUS      current
	DESCRIPTION
	"The number of active endpoints."
	::= {ibmImaStatisticsServer 8}	
	
ibmImaBufferedMessages OBJECT-TYPE
	SYNTAX      CounterBasedGauge64
	MAX-ACCESS  read-only
	STATUS      current
	DESCRIPTION
	"An approximate count of the number of messages (including inflight 
	messages) that are currently buffered on queues and subscriptions on
	the IBM MessageSight server."
	::= {ibmImaStatisticsServer 9}	
	
ibmImaRetainedMessages OBJECT-TYPE
	SYNTAX      CounterBasedGauge64
	MAX-ACCESS  read-only
	STATUS      current
	DESCRIPTION
	"An approximate count of the number of retained messages (including 
	inflight messages) that are currently waiting on topics on the IBM 
	MessageSight server. "
	::= {ibmImaStatisticsServer 10}	
	
ibmImaExpiredMessages OBJECT-TYPE
	SYNTAX      CounterBasedGauge64
	MAX-ACCESS  read-only
	STATUS      current
	DESCRIPTION
	"An approximate count of the number of messages that have expired on
	the IBM MessageSight server."
	::= {ibmImaStatisticsServer 11}		
		 
		 
ibmImaEndpointTable OBJECT-TYPE
	SYNTAX      SEQUENCE OF IMAEndpointTableEntry
	MAX-ACCESS  not-accessible
	STATUS current
	DESCRIPTION "IBM MessageSight server endpoint statistics."
	::= {ibmImaStatus 5}

IMAEndpointTableEntry ::= SEQUENCE {
	ibmImaEndpointColIndex          Integer32,
	ibmImaEndpointName 	        OCTET STRING,
	ibmImaEndpointIpAddr 	        DisplayString,
	ibmImaEndpointEnabled 	        Integer32,
	ibmImaEndpointTotal 	        CounterBasedGauge64,
	ibmImaEndpointActive 	        CounterBasedGauge64,
	ibmImaEndpointMessages 	        CounterBasedGauge64,
	ibmImaEndpointBytes 	        CounterBasedGauge64,
	ibmImaEndpointLastErrorCode 	Integer32,
	ibmImaEndpointConfigTime 	DisplayString,
	ibmImaEndpointResetTime 	DisplayString,
	ibmImaEndpointBadConnections 	CounterBasedGauge64
}

ibmImaEndpointTableEntry OBJECT-TYPE
	SYNTAX      IMAEndpointTableEntry
	MAX-ACCESS  not-accessible
	STATUS current
	DESCRIPTION "Statistics for an IBM MessageSight server endpoint."
	INDEX { ibmImaEndpointColIndex } 
	::= {ibmImaEndpointTable 1}

ibmImaEndpointColIndex OBJECT-TYPE
	SYNTAX      Integer32 (1..65535)
	MAX-ACCESS  read-only
	STATUS      current
	DESCRIPTION
	"Column index of the endpoint"
	::= {ibmImaEndpointTableEntry 1}
	
ibmImaEndpointName OBJECT-TYPE
	SYNTAX      OCTET STRING (SIZE (0..1024))
	MAX-ACCESS  read-only
	STATUS      current
	DESCRIPTION
	"The name of the endpoint."
	::= {ibmImaEndpointTableEntry 2}		
	
ibmImaEndpointIpAddr OBJECT-TYPE
	SYNTAX      DisplayString (SIZE (0..100))
	MAX-ACCESS  read-only
	STATUS      current
	DESCRIPTION
	"The network interface address to which the endpoint is bound."
	::= {ibmImaEndpointTableEntry 3}		
	
ibmImaEndpointEnabled OBJECT-TYPE
	SYNTAX      Integer32
	MAX-ACCESS  read-only
	STATUS      current
	DESCRIPTION
	"Indicates whether the endpoint is enabled. If the endpoint is enabled 
	and the LastErrorCode is zero, this indicates that the endpoint is 
	accepting connections. "
	::= {ibmImaEndpointTableEntry 4}		
	
ibmImaEndpointTotal OBJECT-TYPE
	SYNTAX      CounterBasedGauge64
	MAX-ACCESS  read-only
	STATUS      current
	DESCRIPTION
	"The number of connections that completed through to the protocol 
	handshake since configuration time."
	::= {ibmImaEndpointTableEntry 5}		
	
ibmImaEndpointActive OBJECT-TYPE
	SYNTAX      CounterBasedGauge64
	MAX-ACCESS  read-only
	STATUS      current
	DESCRIPTION
	"The number of connections that are currently active."
	::= {ibmImaEndpointTableEntry 6}		
	
ibmImaEndpointMessages OBJECT-TYPE
	SYNTAX      CounterBasedGauge64
	MAX-ACCESS  read-only
	STATUS      current
	DESCRIPTION
	"The number of messages that are sent or received since configuration 
	time."
	::= {ibmImaEndpointTableEntry 7}		
	
ibmImaEndpointBytes OBJECT-TYPE
	SYNTAX      CounterBasedGauge64
	MAX-ACCESS  read-only
	STATUS      current
	DESCRIPTION
	"The number of bytes that are sent and received since configuration 
	time."
	::= {ibmImaEndpointTableEntry 8}		
	
ibmImaEndpointLastErrorCode OBJECT-TYPE
	SYNTAX      Integer32
	MAX-ACCESS  read-only
	STATUS      current
	DESCRIPTION
	"This value provides an indication of the success of the last 
	configuration of the endpoint. An endpoint is working if Enabled=1 
	and LastErrorCode=0."
	::= {ibmImaEndpointTableEntry 9}		

ibmImaEndpointConfigTime OBJECT-TYPE
	SYNTAX      DisplayString (SIZE (0..100))
	MAX-ACCESS  read-only
	STATUS      current
	DESCRIPTION
	"The time of the last major configuration of an endpoint and the time at 
	which the statistics were reset. The ConfigTime is usually the time at 
	which the endpoint is first enabled."
	::= {ibmImaEndpointTableEntry 10}		

ibmImaEndpointResetTime OBJECT-TYPE
	SYNTAX      DisplayString (SIZE (0..100))
	MAX-ACCESS  read-only
	STATUS      current
	DESCRIPTION
	"Reserved."
	::= {ibmImaEndpointTableEntry 11}		

ibmImaEndpointBadConnections OBJECT-TYPE
	SYNTAX      CounterBasedGauge64
	MAX-ACCESS  read-only
	STATUS      current
	DESCRIPTION
	"The count of connections that failed before the protocol handshake 
	completed."
	::= {ibmImaEndpointTableEntry 12}
	

ibmImaSubscriptionTable OBJECT-TYPE
	SYNTAX      SEQUENCE OF IMASubscriptionTableEntry
	MAX-ACCESS  not-accessible
	STATUS current
	DESCRIPTION "IBM MessageSight server subscription statistics."
	::= {ibmImaStatus 6}

ibmImaSubscriptionTableEntry OBJECT-TYPE
	SYNTAX      IMASubscriptionTableEntry
	MAX-ACCESS  not-accessible
	STATUS current
	DESCRIPTION "Statistics for an IBM MessageSight server subscription."
	INDEX { ibmImaSubscriptionColIndex } 
	::= {ibmImaSubscriptionTable 1}

IMASubscriptionTableEntry ::= SEQUENCE {
	ibmImaSubscriptionColIndex              Integer32,
	ibmImaSubscriptionSubName 	        OCTET STRING,
	ibmImaSubscriptionTopicString 	        OCTET STRING,
	ibmImaSubscriptionClientID 	        OCTET STRING,
	ibmImaSubscriptionIsDurable 	        DisplayString,
	ibmImaSubscriptionBufferedMsgs 	        CounterBasedGauge64,
	ibmImaSubscriptionBufferedMsgsHWM   	CounterBasedGauge64,
	ibmImaSubscriptionBufferedPercent   	Gauge32,
	ibmImaSubscriptionMaxMessages 	        CounterBasedGauge64,
	ibmImaSubscriptionPublishedMsgs     	CounterBasedGauge64,
	ibmImaSubscriptionRejectedMsgs 	        CounterBasedGauge64,
	ibmImaSubscriptionBufferedHWMPercent	Gauge32,
	ibmImaSubscriptionIsShared 	        DisplayString,
	ibmImaSubscriptionConsumers 	        CounterBasedGauge64,
	ibmImaSubscriptionDiscardedMsgs      	CounterBasedGauge64,
	ibmImaSubscriptionExpiredMsgs 	        CounterBasedGauge64,
	ibmImaSubscriptionMessagingPolicy    	OCTET STRING
}

ibmImaSubscriptionColIndex OBJECT-TYPE
	SYNTAX      Integer32 (1..100)
	MAX-ACCESS  read-only
	STATUS      current
	DESCRIPTION
	"Column index of the subscription"
	::= {ibmImaSubscriptionTableEntry 1}

ibmImaSubscriptionSubName OBJECT-TYPE
	SYNTAX      OCTET STRING (SIZE (0..10240))
	MAX-ACCESS  read-only
	STATUS      current
	DESCRIPTION
	"The name that is associated with the subscription. This value can be 
	an empty string for a non-durable subscription."
	::= {ibmImaSubscriptionTableEntry 2}	
	
ibmImaSubscriptionTopicString OBJECT-TYPE
	SYNTAX      OCTET STRING (SIZE (0..65535))
	MAX-ACCESS  read-only
	STATUS      current
	DESCRIPTION
	"The topic on which the subscription is subscribed."
	::= {ibmImaSubscriptionTableEntry 3}

ibmImaSubscriptionClientID OBJECT-TYPE
	SYNTAX      OCTET STRING (SIZE (0..65535))
	MAX-ACCESS  read-only
	STATUS      current
	DESCRIPTION
	"The client ID of the client that owns the subscription."
	::= {ibmImaSubscriptionTableEntry 4}
	
ibmImaSubscriptionIsDurable OBJECT-TYPE
	SYNTAX      DisplayString (SIZE (0..10))
	MAX-ACCESS  read-only
	STATUS      current
	DESCRIPTION
	"Whether the subscription is durable or non-durable."
	::= {ibmImaSubscriptionTableEntry 5}	
	
ibmImaSubscriptionBufferedMsgs OBJECT-TYPE
	SYNTAX      CounterBasedGauge64
	MAX-ACCESS  read-only
	STATUS      current
	DESCRIPTION
	"The number of published messages that are waiting to be sent to the 
	client."
	::= {ibmImaSubscriptionTableEntry 6}
	
ibmImaSubscriptionBufferedMsgsHWM OBJECT-TYPE
	SYNTAX      CounterBasedGauge64
	MAX-ACCESS  read-only
	STATUS      current
	DESCRIPTION
	"The highest number of published messages since the server was started 
	or the subscription was created, whichever is most recent."
	::= {ibmImaSubscriptionTableEntry 7}
	
ibmImaSubscriptionBufferedPercent OBJECT-TYPE
	SYNTAX      Gauge32 (0..100)
	MAX-ACCESS  read-only
	STATUS      current
	DESCRIPTION
	"The percentage of the maximum buffered messages that the current 
	buffered messages represent."
	::= {ibmImaSubscriptionTableEntry 8}
	
ibmImaSubscriptionMaxMessages OBJECT-TYPE
	SYNTAX      CounterBasedGauge64
	MAX-ACCESS  read-only
	STATUS      current
	DESCRIPTION
	"The maximum number of buffered messages that are allowed for this 
	subscription."
	::= {ibmImaSubscriptionTableEntry 9}
	
ibmImaSubscriptionPublishedMsgs OBJECT-TYPE
	SYNTAX      CounterBasedGauge64
	MAX-ACCESS  read-only
	STATUS      current
	DESCRIPTION
	"The number of messages that are published to this subscription since 
	the server was started or the subscription was created, whichever is 
	most recent."
	::= {ibmImaSubscriptionTableEntry 10}
	
ibmImaSubscriptionRejectedMsgs OBJECT-TYPE
	SYNTAX      CounterBasedGauge64
	MAX-ACCESS  read-only
	STATUS      current
	DESCRIPTION
	"The number of messages that are rejected because the maximum number of 
	buffered messages was reached when the messages were published to the 
	subscription. "
	::= {ibmImaSubscriptionTableEntry 11}
	
ibmImaSubscriptionBufferedHWMPercent OBJECT-TYPE
	SYNTAX      Gauge32 (0..100)
	MAX-ACCESS  read-only
	STATUS      current
	DESCRIPTION
	"The peak number of buffered messages, as a percentage of the maximum 
	number of messages that can be buffered."
	::= {ibmImaSubscriptionTableEntry 12}
	
ibmImaSubscriptionIsShared OBJECT-TYPE
	SYNTAX      DisplayString (SIZE (0..10))
	MAX-ACCESS  read-only
	STATUS      current
	DESCRIPTION
	"Whether the subscription is shared."
	::= {ibmImaSubscriptionTableEntry 13}
	
ibmImaSubscriptionConsumers OBJECT-TYPE
	SYNTAX      CounterBasedGauge64
	MAX-ACCESS  read-only
	STATUS      current
	DESCRIPTION
	"The number of consumers that the subscription has."
	::= {ibmImaSubscriptionTableEntry 14}
	
ibmImaSubscriptionDiscardedMsgs OBJECT-TYPE
	SYNTAX      CounterBasedGauge64
	MAX-ACCESS  read-only
	STATUS      current
	DESCRIPTION
	"The number of messages that were not delivered because they were 
	discarded when the buffer became full."
	::= {ibmImaSubscriptionTableEntry 15}
	
ibmImaSubscriptionExpiredMsgs OBJECT-TYPE
	SYNTAX      CounterBasedGauge64
	MAX-ACCESS  read-only
	STATUS      current
	DESCRIPTION
	"The number of messages that were not delivered because they expired."
	::= {ibmImaSubscriptionTableEntry 16}
	
ibmImaSubscriptionMessagingPolicy OBJECT-TYPE
	SYNTAX      OCTET STRING (SIZE (0..1024))
	MAX-ACCESS  read-only
	STATUS      current
	DESCRIPTION
	"The messaging policy that is in use by the subscription."
	::= {ibmImaSubscriptionTableEntry 17}


ibmImaConnectionTable OBJECT-TYPE
	SYNTAX      SEQUENCE OF IMAConnectionTableEntry
	MAX-ACCESS  not-accessible
	STATUS current
	DESCRIPTION "IBM MessageSight server connection statistics."
	::= {ibmImaStatus 7}

ibmImaConnectionTableEntry OBJECT-TYPE
	SYNTAX      IMAConnectionTableEntry
	MAX-ACCESS  not-accessible
	STATUS current
	DESCRIPTION "Statistics for an IBM MessageSight server connection."
	INDEX { ibmImaConnectionColIndex } 
	::= {ibmImaConnectionTable 1}

IMAConnectionTableEntry ::= SEQUENCE {
	ibmImaConnectionColIndex    Integer32,
	ibmImaConnectionName 	    OCTET STRING,
	ibmImaConnectionProtocol    DisplayString,
	ibmImaConnectionClientAddr  DisplayString,
	ibmImaConnectionUserId 	    OCTET STRING,
	ibmImaConnectionEndpoint    OCTET STRING,
	ibmImaConnectionPort	    Integer32,
	ibmImaConnectionConnectTime DisplayString,
	ibmImaConnectionDuration    CounterBasedGauge64,
	ibmImaConnectionReadBytes   CounterBasedGauge64,
	ibmImaConnectionReadMsg     CounterBasedGauge64,
	ibmImaConnectionWriteBytes  CounterBasedGauge64,
	ibmImaConnectionWriteMsg    CounterBasedGauge64
}

ibmImaConnectionColIndex OBJECT-TYPE
	SYNTAX      Integer32 (1..100)
	MAX-ACCESS  read-only
	STATUS      current
	DESCRIPTION
	"Column index of the connection."
	::= {ibmImaConnectionTableEntry 1}			

ibmImaConnectionName OBJECT-TYPE               
	SYNTAX      OCTET STRING (SIZE (0..1024))   
	MAX-ACCESS  read-only
	STATUS      current
	DESCRIPTION
	"The connection name. The client ID is commonly used."                  
	::= {ibmImaConnectionTableEntry 2}    

ibmImaConnectionProtocol OBJECT-TYPE               
	SYNTAX      DisplayString (SIZE (0..100))   
	MAX-ACCESS  read-only
	STATUS      current
	DESCRIPTION
	"The name of the protocol."                  
	::= {ibmImaConnectionTableEntry 3}    
	
ibmImaConnectionClientAddr OBJECT-TYPE               
	SYNTAX      DisplayString (SIZE (0..50))   
	MAX-ACCESS  read-only
	STATUS      current
	DESCRIPTION
	"The client IP address."                  
	::= {ibmImaConnectionTableEntry 4}    
	
ibmImaConnectionUserId OBJECT-TYPE               
	SYNTAX      OCTET STRING (SIZE (0..4096))   
	MAX-ACCESS  read-only
	STATUS      current
	DESCRIPTION
	"The primary user ID."                  
	::= {ibmImaConnectionTableEntry 5}    
	
ibmImaConnectionEndpoint OBJECT-TYPE               
	SYNTAX      OCTET STRING (SIZE (0..1024))   
	MAX-ACCESS  read-only
	STATUS      current
	DESCRIPTION
	"The name of the endpoint."                  
	::= {ibmImaConnectionTableEntry 6}    
	
ibmImaConnectionPort OBJECT-TYPE               
	SYNTAX      Integer32 (1..65535)   
	MAX-ACCESS  read-only
	STATUS      current
	DESCRIPTION
	"The IBM MessageSight server port."                  
	::= {ibmImaConnectionTableEntry 7}    
	
ibmImaConnectionConnectTime OBJECT-TYPE               
	SYNTAX      DisplayString (SIZE (0..100))   
	MAX-ACCESS  read-only
	STATUS      current
	DESCRIPTION
	"The time that the connection is created."                  
	::= {ibmImaConnectionTableEntry 8}    
	
ibmImaConnectionDuration OBJECT-TYPE               
	SYNTAX      CounterBasedGauge64 
	MAX-ACCESS  read-only
	STATUS      current
	DESCRIPTION
	"The duration of the connection in nanoseconds."                  
	::= {ibmImaConnectionTableEntry 9}    
	
ibmImaConnectionReadBytes OBJECT-TYPE               
	SYNTAX      CounterBasedGauge64   
	MAX-ACCESS  read-only
	STATUS      current
	DESCRIPTION
	"The number of bytes that were read since connection time."                  
	::= {ibmImaConnectionTableEntry 10}    
	
ibmImaConnectionReadMsg OBJECT-TYPE               
	SYNTAX      CounterBasedGauge64   
	MAX-ACCESS  read-only
	STATUS      current
	DESCRIPTION
	"The number of messages that were read since connection time."                  
	::= {ibmImaConnectionTableEntry 11}    
	
ibmImaConnectionWriteBytes OBJECT-TYPE               
	SYNTAX      CounterBasedGauge64   
	MAX-ACCESS  read-only
	STATUS      current
	DESCRIPTION
	"The number of bytes written since connection time."                  
	::= {ibmImaConnectionTableEntry 12}   
	
ibmImaConnectionWriteMsg OBJECT-TYPE             
	SYNTAX      CounterBasedGauge64  
	MAX-ACCESS  read-only
	STATUS      current
	DESCRIPTION
	"The number of messages that are written since connection time."                 
	::= {ibmImaConnectionTableEntry 13}  
	
ibmImaTopicTable OBJECT-TYPE
	SYNTAX      SEQUENCE OF IMATopicTableEntry
	MAX-ACCESS  not-accessible
	STATUS current
	DESCRIPTION "IBM MessageSight server topic statistics."
	::= {ibmImaStatus 8}

ibmImaTopicTableEntry OBJECT-TYPE
	SYNTAX      IMATopicTableEntry
	MAX-ACCESS  not-accessible
	STATUS current
	DESCRIPTION "The statistics for an IBM MessageSight server topic."
	INDEX { ibmImaTopicColIndex } 
	::= {ibmImaTopicTable 1}

IMATopicTableEntry ::= SEQUENCE {
	ibmImaTopicColIndex         Integer32,
	ibmImaTopicTopicString 	    OCTET STRING,
	ibmImaTopicSubscriptions    CounterBasedGauge64,
	ibmImaTopicResetTime 	    DisplayString,
	ibmImaTopicPublishedMsgs    CounterBasedGauge64,
	ibmImaTopicRejectedMsgs     CounterBasedGauge64,
	ibmImaTopicFailedPublishes  CounterBasedGauge64
}

ibmImaTopicColIndex OBJECT-TYPE                 
	SYNTAX      Integer32 (1..100) 
	MAX-ACCESS  read-only
	STATUS      current
	DESCRIPTION
	"Column index of a topic."                     
	::= {ibmImaTopicTableEntry 1}		             	
	
ibmImaTopicTopicString OBJECT-TYPE                 
	SYNTAX      OCTET STRING (SIZE (0..65535))   
	MAX-ACCESS  read-only
	STATUS      current
	DESCRIPTION
	"The topic that is being monitored. The topic string always contains a 
	wildcard."                     
	::= {ibmImaTopicTableEntry 2}		             	
	
ibmImaTopicSubscriptions OBJECT-TYPE                 
	SYNTAX      CounterBasedGauge64   
	MAX-ACCESS  read-only
	STATUS      current
	DESCRIPTION
	"The number of active subscriptions on the topics that are monitored. 
	The figure shows all active subscriptions that match the wildcarded 
	topic string."                     
	::= {ibmImaTopicTableEntry 3}		             	
	
ibmImaTopicResetTime OBJECT-TYPE                 
	SYNTAX      DisplayString (SIZE (0..100))   
	MAX-ACCESS  read-only
	STATUS      current
	DESCRIPTION
	"The time at which the statistics for the topic were reset. The	reset 
	time is usually the time when the topic monitor is created."                     
	::= {ibmImaTopicTableEntry 4}		             		
	
ibmImaTopicPublishedMsgs OBJECT-TYPE                 
	SYNTAX      CounterBasedGauge64   
	MAX-ACCESS  read-only
	STATUS      current
	DESCRIPTION
	"The number of messages that are successfully published to a topic that 
	matches the wildcarded topic string."                     
	::= {ibmImaTopicTableEntry 5}		             		
	
ibmImaTopicRejectedMsgs OBJECT-TYPE                 
	SYNTAX      CounterBasedGauge64   
	MAX-ACCESS  read-only
	STATUS      current
	DESCRIPTION
	"The number of messages that are rejected by one or more subscriptions 
	where the quality of service level did not cause the publish request 
	to fail."                     
	::= {ibmImaTopicTableEntry 6}		             			
	
ibmImaTopicFailedPublishes OBJECT-TYPE                 
	SYNTAX      CounterBasedGauge64   
	MAX-ACCESS  read-only
	STATUS      current
	DESCRIPTION
	"The number of publish requests that failed because the message is 
	rejected by one or more subscriptions."                     
	::= {ibmImaTopicTableEntry 7}		             	
	
	
ibmImaNotifications OBJECT IDENTIFIER ::= {ibmImaManagement 2}
ibmImaNotificationCommonElements OBJECT IDENTIFIER ::= {ibmImaNotifications 1}

ibmImaNotificationImaVersion OBJECT-TYPE
    SYNTAX      DisplayString
    MAX-ACCESS  accessible-for-notify
    STATUS      current
    DESCRIPTION
       "IBM MessageSight server version."
    ::= { ibmImaNotificationCommonElements 1 }

ibmImaNotificationImaNodeName OBJECT-TYPE
    SYNTAX      DisplayString
    MAX-ACCESS  accessible-for-notify
    STATUS      current
    DESCRIPTION
       "IBM MessageSight appliance node name."
    ::= { ibmImaNotificationCommonElements 2 }

ibmImaNotificationEventTime OBJECT-TYPE
    SYNTAX      DisplayString
    MAX-ACCESS  accessible-for-notify
    STATUS      current
    DESCRIPTION
       "The date and time that the event occurred."
    ::= { ibmImaNotificationCommonElements 3 }

ibmImaNotificationObjectType OBJECT-TYPE
    SYNTAX      DisplayString
    MAX-ACCESS  accessible-for-notify
    STATUS      current
    DESCRIPTION
       "The type of object that is generating the event."
    ::= { ibmImaNotificationCommonElements 4 }

ibmImaNotificationMemoryEvent OBJECT IDENTIFIER ::= {ibmImaNotifications 2}
ibmImaNotificationMemoryEventElements OBJECT IDENTIFIER ::= {ibmImaNotificationMemoryEvent 1}
ibmImaNotificationMemoryEventControl OBJECT IDENTIFIER ::= {ibmImaNotificationMemoryEvent 3}
ibmImaNotificationMemoryEventDefinitions OBJECT IDENTIFIER ::= {ibmImaNotificationMemoryEvent 2}

ibmImaNotificationMemoryTotalBytes OBJECT-TYPE
    SYNTAX      CounterBasedGauge64
    MAX-ACCESS  accessible-for-notify
    STATUS      current
    DESCRIPTION
       "The total amount of physical memory on IBM MessageSight."
    ::= { ibmImaNotificationMemoryEventElements 1 }

ibmImaNotificationMemoryFreeBytes OBJECT-TYPE
    SYNTAX      CounterBasedGauge64
    MAX-ACCESS  accessible-for-notify
    STATUS      current
    DESCRIPTION
       "The amount of physical memory that is available on IBM MessageSight."
    ::= { ibmImaNotificationMemoryEventElements 2 }

ibmImaNotificationMemoryFreePercent OBJECT-TYPE
    SYNTAX      Gauge32 (0..100)
    MAX-ACCESS  accessible-for-notify
    STATUS      current
    DESCRIPTION
       "The amount of free memory as a percentage of total physical memory on 
       IBM MessageSight."
    ::= { ibmImaNotificationMemoryEventElements 3 }

ibmImaNotificationVirtualMemoryBytes OBJECT-TYPE
    SYNTAX      CounterBasedGauge64
    MAX-ACCESS  accessible-for-notify
    STATUS      current
    DESCRIPTION
       "The amount of virtual memory that is being used by IBM MessageSight."
    ::= { ibmImaNotificationMemoryEventElements 4 }

ibmImaNotificationResidentSetBytes OBJECT-TYPE
    SYNTAX      CounterBasedGauge64
    MAX-ACCESS  accessible-for-notify
    STATUS      current
    DESCRIPTION
       "The amount of physical memory that is being used by IBM MessageSight."
    ::= { ibmImaNotificationMemoryEventElements 5 }

ibmImaNotificationMessagePayloads OBJECT-TYPE
    SYNTAX      CounterBasedGauge64
    MAX-ACCESS  accessible-for-notify
    STATUS      current
    DESCRIPTION
       "The amount of memory that is being consumed 
        by IBM MessageSight for message payloads.
       "
    ::= { ibmImaNotificationMemoryEventElements 6 }

ibmImaNotificationPublishSubscribe OBJECT-TYPE
    SYNTAX      CounterBasedGauge64
    MAX-ACCESS  accessible-for-notify
    STATUS      current
    DESCRIPTION
       "The amount of memory that is being consumed by 
        IBM MessageSight for publish/subscribe data structures.
       "
    ::= { ibmImaNotificationMemoryEventElements 7 }

ibmImaNotificationDestinations OBJECT-TYPE
    SYNTAX      CounterBasedGauge64
    MAX-ACCESS  accessible-for-notify
    STATUS      current
    DESCRIPTION
       "The amount of memory that is being consumed by 
        IBM MessageSight for destinations on which messages 
        can be buffered."
    ::= { ibmImaNotificationMemoryEventElements 8 }

ibmImaNotificationCurrentActivity OBJECT-TYPE
    SYNTAX      CounterBasedGauge64
    MAX-ACCESS  accessible-for-notify
    STATUS      current
    DESCRIPTION
       "The amount of memory that is being consumed by 
        IBM MessageSight for current activity.
       "
    ::= { ibmImaNotificationMemoryEventElements 9 }

ibmImaNotificationClientStates OBJECT-TYPE
    SYNTAX      CounterBasedGauge64
    MAX-ACCESS  accessible-for-notify
    STATUS      current
    DESCRIPTION
       "The amount of memory that is being consumed by 
        IBM MessageSight for connected and disconnected clients.
       "
    ::= { ibmImaNotificationMemoryEventElements 10 }

ibmImaNotificationMemoryUsageWarning NOTIFICATION-TYPE
    OBJECTS {
        ibmImaNotificationImaVersion,
        ibmImaNotificationImaNodeName,
        ibmImaNotificationEventTime,
        ibmImaNotificationObjectType,
        ibmImaNotificationMemoryTotalBytes,
        ibmImaNotificationMemoryFreeBytes,
        ibmImaNotificationMemoryFreePercent,
        ibmImaNotificationVirtualMemoryBytes,
        ibmImaNotificationResidentSetBytes,
        ibmImaNotificationMessagePayloads,
        ibmImaNotificationPublishSubscribe,
        ibmImaNotificationDestinations,
        ibmImaNotificationCurrentActivity,
        ibmImaNotificationClientStates    }
    STATUS current
    DESCRIPTION
        "This notification indicates that memory usage is getting 
         higher than the warning threshold; generally more than 65%, 
         but less than 85%."
    ::= { ibmImaNotificationMemoryEventDefinitions 1 }

ibmImaNotificationMemoryUsageAlert NOTIFICATION-TYPE
    OBJECTS {
        ibmImaNotificationImaVersion,
        ibmImaNotificationImaNodeName,
        ibmImaNotificationEventTime,
        ibmImaNotificationObjectType,
        ibmImaNotificationMemoryTotalBytes,
        ibmImaNotificationMemoryFreeBytes,
        ibmImaNotificationMemoryFreePercent,
        ibmImaNotificationVirtualMemoryBytes,
        ibmImaNotificationResidentSetBytes,
        ibmImaNotificationMessagePayloads,
        ibmImaNotificationPublishSubscribe,
        ibmImaNotificationDestinations,
        ibmImaNotificationCurrentActivity,
        ibmImaNotificationClientStates    }
    STATUS current
    DESCRIPTION
        "This notification indicates that memory usage is getting 
         higher than the alert threshold; more than 85%."
    ::= { ibmImaNotificationMemoryEventDefinitions 2 }


ibmImaMemoryUsageWarningEnable OBJECT-TYPE
	SYNTAX     INTEGER {                                              
                        enable(1),               
                        disable(2)                                                    
                }             
	MAX-ACCESS  read-write
	STATUS      current
	DESCRIPTION
	"Enable/disable the memory usage warning trap."
	::= {ibmImaNotificationMemoryEventControl 1}		

ibmImaMemoryUsageWarningThreshold OBJECT-TYPE
	SYNTAX     Integer32  (0..100)                                             
	MAX-ACCESS  read-write
	STATUS      current
	DESCRIPTION
	"The memory usage warning threshold, as a percentage of total memory. "
	::= {ibmImaNotificationMemoryEventControl 2}		

ibmImaMemoryUsageAlertEnable OBJECT-TYPE
	SYNTAX     INTEGER {                                              
                        enable(1),               
                        disable(2)                                                    
                }             
	MAX-ACCESS  read-write
	STATUS      current
	DESCRIPTION
	"Enable/disable the memory usage alert trap."
	::= {ibmImaNotificationMemoryEventControl 3}		

ibmImaMemoryUsageAlertThreshold OBJECT-TYPE
	SYNTAX     Integer32   (0..100)                                            
	MAX-ACCESS  read-write
	STATUS      current
	DESCRIPTION
	"The memory usage alert threshold, as a percentage of total memory."
	::= {ibmImaNotificationMemoryEventControl 4}		

ibmImaMemoryUsageWarningDuration OBJECT-TYPE
	SYNTAX     Integer32                                               
	MAX-ACCESS  read-write
	STATUS      current
	DESCRIPTION
	"The duration time of a memory usage warning event, in seconds."
	::= {ibmImaNotificationMemoryEventControl 5}		

ibmImaNotificationStoreEvent OBJECT IDENTIFIER ::= {ibmImaNotifications 3}
ibmImaNotificationStoreEventElements OBJECT IDENTIFIER ::= {ibmImaNotificationStoreEvent 1}
ibmImaNotificationStoreEventDefinitions OBJECT IDENTIFIER ::= {ibmImaNotificationStoreEvent 2}
ibmImaNotificationStoreEventControl OBJECT IDENTIFIER ::= {ibmImaNotificationStoreEvent 3}

ibmImaNotificationStoreDiskUsedPercent OBJECT-TYPE
	SYNTAX      Gauge32 (0..100)
	MAX-ACCESS  accessible-for-notify
	STATUS      current
	DESCRIPTION
	"The percentage of disk space that is being used."
	::= {ibmImaNotificationStoreEventElements 1} 

ibmImaNotificationStoreDiskFreeBytes OBJECT-TYPE
	SYNTAX      CounterBasedGauge64
	MAX-ACCESS  accessible-for-notify
	STATUS      current
	DESCRIPTION
	"The amount of disk space, in bytes, that is available."
	::= {ibmImaNotificationStoreEventElements 2} 
	
ibmImaNotificationStoreMemoryUsedPercent OBJECT-TYPE
	SYNTAX      Gauge32 (0..100)
	MAX-ACCESS  accessible-for-notify
	STATUS      current
	DESCRIPTION
	"The percentage of persistent memory that is used, and, therefore, is not available."
	::= {ibmImaNotificationStoreEventElements 3} 

ibmImaNotificationStoreMemoryTotalBytes OBJECT-TYPE
	SYNTAX      CounterBasedGauge64
	MAX-ACCESS  accessible-for-notify
	STATUS      current
	DESCRIPTION
	"The total amount of persistent memory, in bytes, on IBM MessageSight."
	::= {ibmImaNotificationStoreEventElements 4}
	
ibmImaNotificationStorePool1TotalBytes OBJECT-TYPE
	SYNTAX      CounterBasedGauge64
	MAX-ACCESS  accessible-for-notify
	STATUS      current
	DESCRIPTION
	"The amount of memory, in bytes, in pool 1."
	::= {ibmImaNotificationStoreEventElements 5}
	
ibmImaNotificationStorePool1UsedBytes OBJECT-TYPE
	SYNTAX      CounterBasedGauge64
	MAX-ACCESS  accessible-for-notify
	STATUS      current
	DESCRIPTION
	"The amount of memory, in bytes, that is currently in use in 
	pool 1."
	::= {ibmImaNotificationStoreEventElements 6}
	
ibmImaNotificationStorePool1UsedPercent OBJECT-TYPE
	SYNTAX      Gauge32 (0..100)
	MAX-ACCESS  accessible-for-notify
	STATUS      current
	DESCRIPTION
	"The percentage of memory that is in use in pool 1."
	::= {ibmImaNotificationStoreEventElements 7}
	
ibmImaNotificationStorePool1RecordsLimitBytes OBJECT-TYPE
	SYNTAX      CounterBasedGauge64
	MAX-ACCESS  accessible-for-notify
	STATUS      current
	DESCRIPTION
	"The overall amount of memory, in bytes, that can be used by client 
	applications. When the pool 1 record limit is reached, records cannot be 
	created for topics with retained messages, durable subscriptions, queues, 
	clients, and connectivity with WebSphere MQ queue managers."
	::= {ibmImaNotificationStoreEventElements 8}
	
ibmImaNotificationStorePool1RecordsUsedBytes OBJECT-TYPE
	SYNTAX      CounterBasedGauge64
	MAX-ACCESS  accessible-for-notify
	STATUS      current
	DESCRIPTION
	"The amount of memory, in bytes, that is being used for client 
	records."
	::= {ibmImaNotificationStoreEventElements 9}
	
ibmImaNotificationStorePool2TotalBytes OBJECT-TYPE
	SYNTAX      CounterBasedGauge64
	MAX-ACCESS  accessible-for-notify
	STATUS      current
	DESCRIPTION
	"The amount of memory, in bytes, in pool 2."
	::= {ibmImaNotificationStoreEventElements 10}
	
ibmImaNotificationStorePool2UsedBytes OBJECT-TYPE
	SYNTAX      CounterBasedGauge64
	MAX-ACCESS  accessible-for-notify
	STATUS      current
	DESCRIPTION
	"The amount of memory, in bytes, that is currently in use in 
	pool 2."
	::= {ibmImaNotificationStoreEventElements 11}
	
ibmImaNotificationStorePool2UsedPercent OBJECT-TYPE
	SYNTAX      Gauge32 (0..100)
	MAX-ACCESS  accessible-for-notify
	STATUS      current
	DESCRIPTION
	"The percentage of memory that is in use in pool 2."
	::= {ibmImaNotificationStoreEventElements 12}

ibmImaNotificationStoreDiskUsageWarning NOTIFICATION-TYPE
    OBJECTS {
        ibmImaNotificationImaVersion,
        ibmImaNotificationImaNodeName,
        ibmImaNotificationEventTime,
        ibmImaNotificationObjectType,
        ibmImaNotificationStoreDiskUsedPercent,
        ibmImaNotificationStoreDiskFreeBytes,
        ibmImaNotificationStoreMemoryUsedPercent,
        ibmImaNotificationStoreMemoryTotalBytes,
        ibmImaNotificationStorePool1TotalBytes,
        ibmImaNotificationStorePool1UsedBytes,
        ibmImaNotificationStorePool1UsedPercent,
        ibmImaNotificationStorePool1RecordsLimitBytes,
        ibmImaNotificationStorePool1RecordsUsedBytes,
        ibmImaNotificationStorePool2TotalBytes,
        ibmImaNotificationStorePool2UsedBytes,
        ibmImaNotificationStorePool2UsedPercent}
    STATUS current
    DESCRIPTION
        "This notification indicates that store disk usage is getting 
         higher than the warning threshold; generally more than 80%, 
         but less than 90%."
    ::= { ibmImaNotificationStoreEventDefinitions 1 }

ibmImaNotificationStoreDiskUsageAlert NOTIFICATION-TYPE
    OBJECTS {
        ibmImaNotificationImaVersion,
        ibmImaNotificationImaNodeName,
        ibmImaNotificationEventTime,
        ibmImaNotificationObjectType,
        ibmImaNotificationStoreDiskUsedPercent,
        ibmImaNotificationStoreDiskFreeBytes,
        ibmImaNotificationStoreMemoryUsedPercent,
        ibmImaNotificationStoreMemoryTotalBytes,
        ibmImaNotificationStorePool1TotalBytes,
        ibmImaNotificationStorePool1UsedBytes,
        ibmImaNotificationStorePool1UsedPercent,
        ibmImaNotificationStorePool1RecordsLimitBytes,
        ibmImaNotificationStorePool1RecordsUsedBytes,
        ibmImaNotificationStorePool2TotalBytes,
        ibmImaNotificationStorePool2UsedBytes,
        ibmImaNotificationStorePool2UsedPercent}
    STATUS current
    DESCRIPTION
        "This notification indicates that store disk usage is getting 
         higher than the alert threshold; more than 90%."
    ::= { ibmImaNotificationStoreEventDefinitions 2 }

ibmImaNotificationStorePool1MemoryLowAlert NOTIFICATION-TYPE
    OBJECTS {
        ibmImaNotificationImaVersion,
        ibmImaNotificationImaNodeName,
        ibmImaNotificationEventTime,
        ibmImaNotificationObjectType,
        ibmImaNotificationStoreDiskUsedPercent,
        ibmImaNotificationStoreDiskFreeBytes,
        ibmImaNotificationStoreMemoryUsedPercent,
        ibmImaNotificationStoreMemoryTotalBytes,
        ibmImaNotificationStorePool1TotalBytes,
        ibmImaNotificationStorePool1UsedBytes,
        ibmImaNotificationStorePool1UsedPercent,
        ibmImaNotificationStorePool1RecordsLimitBytes,
        ibmImaNotificationStorePool1RecordsUsedBytes,
        ibmImaNotificationStorePool2TotalBytes,
        ibmImaNotificationStorePool2UsedBytes,
        ibmImaNotificationStorePool2UsedPercent}
    STATUS current
    DESCRIPTION
        "This notification indicates that store pool 1 memory used is  
         close to the limit. Fewer than 4096 bytes remain."
    ::= { ibmImaNotificationStoreEventDefinitions 3 }


ibmImaStoreDiskUsageWarningEnable OBJECT-TYPE
	SYNTAX     INTEGER {                                              
                        enable(1),               
                        disable(2)                                                    
                }             
	MAX-ACCESS  read-write
	STATUS      current
	DESCRIPTION
	"Enable/disable the store disk usage warning trap."
	::= {ibmImaNotificationStoreEventControl 1}		

ibmImaStoreDiskUsageWarningThreshold OBJECT-TYPE
	SYNTAX     Integer32  (0..100)                                             
	MAX-ACCESS  read-write
	STATUS      current
	DESCRIPTION
	"The store disk usage warning threshold, as a percentage of total disk size."
	::= {ibmImaNotificationStoreEventControl 2}		

ibmImaStoreDiskUsageAlertEnable OBJECT-TYPE
	SYNTAX     INTEGER {                                              
                        enable(1),               
                        disable(2)                                                    
                }             
	MAX-ACCESS  read-write
	STATUS      current
	DESCRIPTION
	"Enable/disable the store disk usage alert trap."
	::= {ibmImaNotificationStoreEventControl 3}		

ibmImaStoreDiskUsageAlertThreshold OBJECT-TYPE
	SYNTAX     Integer32   (0..100)                                            
	MAX-ACCESS  read-write
	STATUS      current
	DESCRIPTION
	"The store disk usage alert threshold, as a percentage of total disk size."
	::= {ibmImaNotificationStoreEventControl 4}		

ibmImaStoreDiskUsageWarningDuration OBJECT-TYPE
	SYNTAX     Integer32                                               
	MAX-ACCESS  read-write
	STATUS      current
	DESCRIPTION
	"The duration time of a store disk usage warning event, in seconds."
	::= {ibmImaNotificationStoreEventControl 5}		

ibmImaStorePool1MemoryLowAlertEnable OBJECT-TYPE
	SYNTAX     INTEGER {                                              
                        enable(1),               
                        disable(2)                                                    
                }             
	MAX-ACCESS  read-write
	STATUS      current
	DESCRIPTION
	"Enable/disable the store pool 1 memory low alert trap."
	::= {ibmImaNotificationStoreEventControl 6}		

ibmImaStorePool1MemoryLowAlertThreshold OBJECT-TYPE
	SYNTAX     Integer32                                               
	MAX-ACCESS  read-write
	STATUS      current
	DESCRIPTION
	"The store pool 1 memory low alert threshold, in bytes remaining until the limit is reached."
	::= {ibmImaNotificationStoreEventControl 7}		

END
